/*
 * Copyright (c) 2015 Hewlett-Packard Development Company, L.P. and others.  All rights reserved.
 *
 * This program and the accompanying materials are made available under the
 * terms of the Eclipse Public License v1.0 which accompanies this distribution,
 * and is available at http://www.eclipse.org/legal/epl-v10.html
 */
module didm-identification {

    namespace "urn:opendaylight:params:xml:ns:yang:didm:identification";
    prefix id;

    import yang-ext {prefix ext; revision-date "2013-07-09";}
    import opendaylight-inventory {prefix inv; revision-date "2013-08-19";}

    revision "2015-02-02" {
      description "Initial implementation.";
    }

    augment "/inv:nodes/inv:node" {
        ext:augment-identifier "device-type";
        leaf device-type {
            type string;
        }
    }
}
