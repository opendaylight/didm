/*
 * Copyright (c) 2015 Hewlett-Packard Development Company, L.P. and others.  All rights reserved.
 *
 * This program and the accompanying materials are made available under the
 * terms of the Eclipse Public License v1.0 which accompanies this distribution,
 * and is available at http://www.eclipse.org/legal/epl-v10.html
 */
module openflow-feature {

    namespace "urn:opendaylight:params:xml:ns:yang:didm:drivers:openflow";
    prefix of;

    import opendaylight-inventory {prefix inv; revision-date "2013-08-19";}
    import opendaylight-flow-types {prefix flow;revision-date "2013-10-26";}

    revision "2015-02-11" { description "Initial implementation."; }

    rpc adjust-flow {
        description "Adjust the provided flow, if necessary, based on the node's actual capabilities.
                     Depending on the node's capabilities, multiple flows may be returned.";

        input {

            uses "inv:node-context-ref";

            container flow {
               description "The flow to be adjusted.";
               uses flow:flow;
            }
        }

        output {
           list flow {
              description "The node-compatible flow(s) equivalent to the input flow.";
              uses flow:flow;
           }
        }
    }

}
