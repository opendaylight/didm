/*
 * Copyright (c) 2015 Hewlett-Packard Development Company, L.P. and others.  All rights reserved.
 *
 * This program and the accompanying materials are made available under the
 * terms of the Eclipse Public License v1.0 which accompanies this distribution,
 * and is available at http://www.eclipse.org/legal/epl-v10.html
 */
module hp-3800 {

    namespace "urn:opendaylight:params:xml:ns:yang:didm:hp";
    prefix hp-3800;

    import config { prefix config; revision-date 2013-04-05; }
    import opendaylight-md-sal-binding { prefix mdsal; revision-date 2013-10-28; }

    revision "2015-02-18" { description "Initial implementation."; }

    identity hp-3800-provider {
            base config:module-type;

            config:java-name-prefix HP3800;
    }

    augment "/config:modules/config:module/config:configuration" {
        case hp-3800-provider {
            when "/config:modules/config:module/config:type = 'hp-3800-provider'";

           container data-broker {
                uses config:service-ref {
                    refine type {
                        mandatory false;
                        config:required-identity mdsal:binding-async-data-broker;
                    }
                }
            }

            container rpc-registry {
               uses config:service-ref {
                   refine type {
                       mandatory true;
                       config:required-identity mdsal:binding-rpc-registry;
                   }
               }
            }
        }
    }

}
